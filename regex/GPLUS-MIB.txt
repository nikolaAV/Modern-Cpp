GPLUS-MIB DEFINITIONS ::= BEGIN

--- Genesys G-Plus Adapters MIB v8.0.2 (Draft)

IMPORTS
	DisplayString, TruthValue FROM SNMPv2-TC

	MODULE-IDENTITY,
	OBJECT-TYPE,
	enterprises,
	Unsigned32,
	TimeTicks,
	Counter64  FROM SNMPv2-SMI;

---
--- MIB High Level description
---

genesys MODULE-IDENTITY
	LAST-UPDATED "201510140000Z"
	ORGANIZATION "Genesys Telecommunications Labs"
	CONTACT-INFO
		"Postal: 2001 Junipero Serra Blvd
		Daly City, CA 94014
		US
		Tel: +1 888 GENESYS
		Fax: +1 415 437 1260
		email: support@genesyslab.com"
	DESCRIPTION
	"Collection of managed objects that provides for remote
	management of server applications which belong to 'G+ Adapters Product Line'."

	REVISION "201510150000Z"
	DESCRIPTION
		"Version 8.0.2.(Draft)"
::= { enterprises 1729 }

-- #############################################################################
-- Object Identifiers
-- #############################################################################


-- gplus root node, ask genesys about identifier uniquely associated to the 'gplus' node 
gplus OBJECT IDENTIFIER
	::= { genesys 4321 }

gpApps OBJECT IDENTIFIER
	::= { gplus 1 }

gpCommon OBJECT IDENTIFIER
	::= { gplus 99 }

-- Standalone executable part of Genesys Communication Server for Siebel CRM
gcs OBJECT IDENTIFIER
	::= { gpApps 1 }

-- Load Libraty part of Genesys Communication Server for Siebel CRM (reserved)
gcd OBJECT IDENTIFIER
	::= { gpApps 2 }

-- Open Media Server (reserved)
oms OBJECT IDENTIFIER
	::= { gpApps 3 }

gpConfig OBJECT IDENTIFIER
	::= { gpCommon 1 }

gpScalar OBJECT IDENTIFIER
	::= { gpCommon 2 }

gpTraps OBJECT IDENTIFIER
	::= { gpCommon 100 }

-- #############################################################################
-- gpConfig BRANCH
-- #############################################################################

gpAppConfigName OBJECT-TYPE
	SYNTAX		DisplayString
	MAX-ACCESS	read-only
	STATUS		current
	DESCRIPTION
        "gpAppConfigName: The name of the application on the
        Configuration Server."
    ::= { gpConfig 1 }

gpConfigDBID OBJECT-TYPE
	SYNTAX		Unsigned32
	MAX-ACCESS	not-accessible
	STATUS		current
	DESCRIPTION
	    "gpConfigDBID: DB IDs are generated by the Configuration Server when new
	    applications are added. The IDs are unique within a given configuration environment.
	    DB IDs of deleted applications are not reused within the same power cycle of the 
	    Configuration Server."
	::= { gpConfig 2 }



-- #############################################################################
-- gpScalar BRANCH
-- #############################################################################

gpProcessID OBJECT-TYPE
	SYNTAX		Unsigned32
	MAX-ACCESS	not-accessible
	STATUS		current
	DESCRIPTION
	    "gpProcessID: The PID of running process."
	::= { gpScalar 1 }

gpResourceAvalability OBJECT-TYPE
	SYNTAX		TruthValue
	MAX-ACCESS	not-accessible
	STATUS		current
	DESCRIPTION
	    "gpResourceAvalability: Variable of boolen type. 'true' means that a resource is in operation;
	    otherwise, 'false' - a resource is inavailable"
	::= { gpScalar 2 }

gpRequestDescription OBJECT-TYPE
	SYNTAX		DisplayString
	MAX-ACCESS	not-accessible
	STATUS		current
	DESCRIPTION
	    "gpRequestDescription: A string that contains request description."
	::= { gpScalar 3 }

gpSocketID OBJECT-TYPE
	SYNTAX		Unsigned32
	MAX-ACCESS	not-accessible
	STATUS		current
	DESCRIPTION
	    "gpSocketID: ID of the network socket."
	::= { gpScalar 4 }

gpSecond OBJECT-TYPE
	SYNTAX		Unsigned32
	MAX-ACCESS	not-accessible
	STATUS		current
	DESCRIPTION
	    "gpSecond: time in seconds."
	::= { gpScalar 5 }

gpMillisecond OBJECT-TYPE
	SYNTAX		Unsigned32
	MAX-ACCESS	not-accessible
	STATUS		current
	DESCRIPTION
	    "gpSecond: time in milliseconds."
	::= { gpScalar 6 }


-- #############################################################################
-- gcs BRANCH Genesys Communication Server for Siebel CRM
-- #############################################################################

gcsTraps OBJECT IDENTIFIER
	::= { gcs 100 }

gpNetParsingErrorTrap NOTIFICATION-TYPE
  OBJECTS { gpAppConfigName, gpSocketID }
  STATUS  current
  DESCRIPTION
    "Notification message reporting about error while parsing network communication
     packets."
  ::= {gcsTraps 1}

gpMultimediaServiceTrap NOTIFICATION-TYPE
  OBJECTS { gpAppConfigName, gpResourceAvailability }
  STATUS  current
  DESCRIPTION
    "Notification message reporting that a Multimedia functions of adapter
     is available or not."
  ::= {gcsTraps 2}

gpVoiceServiceTrap NOTIFICATION-TYPE
  OBJECTS { gpAppConfigName, gpResourceAvailability }
  STATUS  current
  DESCRIPTION
    "Notification message reporting that a Voice functions of adapter
     is available or not."
  ::= {gcsTraps 3}

gpProcessIDTrap NOTIFICATION-TYPE
  OBJECTS { gpAppConfigName, gpProcessID }
  STATUS  current
  DESCRIPTION
    "Notification message reporting a PID of running application."
  ::= {gcsTraps 4}

gpG2SRequestExpiredTrap NOTIFICATION-TYPE
  OBJECTS { gpAppConfigName, gpRequestDescription }
  STATUS  current
  DESCRIPTION
    "Notification message reporting that a request sent from Genesys G+ server 
     to Siebel side is expired for the particular agent session."
  ::= {gcsTraps 5}

gpS2GRequestExpiredTrap NOTIFICATION-TYPE
  OBJECTS { gpAppConfigName, gpRequestDescription }
  STATUS  current
  DESCRIPTION
    "Notification message reporting that a request sent from Siebel side to 
     Genesys G+ server side is expired for the particular agent session."
  ::= {gcsTraps 6}

gpG2SAvgReqProcessingTimeTrap NOTIFICATION-TYPE
  OBJECTS { gpAppConfigName, gpMillisecond }
  STATUS  current
  DESCRIPTION
    "Notification message reporting average request processing time for configured
     time interval for requests sent from Genesys G+ server to Siebel side."
  ::= {gcsTraps 7}

gpS2GAvgReqProcessingTimeTrap NOTIFICATION-TYPE
  OBJECTS { gpAppConfigName, gpMillisecond }
  STATUS  current
  DESCRIPTION
    "Notification message reporting average request processing time for configured
     time interval for requests sent from Siebel side to Genesys G+ server."
  ::= {gcsTraps 8}

END
